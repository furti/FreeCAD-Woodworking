import FreeCAD
import FreeCADGui


o = FreeCADGui.Selection.getSelection()[0]

o.addProperty("App::PropertyLength", "Breite", "Info", "Breite").Breite=1.0
o.addProperty("App::PropertyLength", "Laenge", "Info", "Laenge").Laenge=1.0
o.addProperty("App::PropertyLength", "Staerke", "Info", "Staerke").Staerke=1.0

o.setExpression('Breite', u'Sketch.Constraints.Breite')
o.setExpression('Laenge', u'Sketch.Constraints.Laenge')
o.setExpression('Staerke', u'Pad.Length')
